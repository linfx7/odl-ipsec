module ipsec-impl {
    yang-version 1;
    namespace "urn:opendaylight:params:xml:ns:yang:ipsec:impl";
    prefix "ipsec-impl";

    import config { prefix config; revision-date 2013-04-05; }
    import opendaylight-md-sal-binding { prefix md-sal-binding; revision-date 2013-10-28;}

    description
        "Service definition for ipsec project";

    revision "2014-12-10" {
        description
            "Initial revision";
    }

    identity ipsec {
        base config:module-type;
        config:java-name-prefix IPsec;
    }

    augment "/config:modules/config:module/config:configuration" {
        case ipsec {
            when "/config:modules/config:module/config:type = 'ipsec'";
            container broker {
                uses config:service-ref {
                    refine type {
                        mandatory true;
                        config:required-identity md-sal-binding:binding-broker-osgi-registry;
                    }
                }
            }
        }
    }
}
