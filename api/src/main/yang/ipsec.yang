module IPsec {
    yang-version 1;
    namespace "urn:opendaylight:params:xml:ns:yang:ipsec";
    prefix "ipsec";

    revision "2015-01-05" {
        description "Initial revision of ipsec model";
    }

    grouping src-netaddress {
        leaf source {
            type string;
        }
        leaf srcPrefixLen {
            type int8;
        }
    }

    grouping dst-netaddress {
        leaf destination {
            type string;
        }
        leaf dstPrefixLen {
            type int8;
        }
    }

    grouping connection {
        leaf connectionType {
            type string;
        }
        leaf name {
            type string;
        }
        leaf keyexchange {
            type string;
        }
        leaf ike {
            type string;
        }
        leaf ah {
            type string;
        }
        leaf esp {
            type string;
        }
        leaf authby {
            type string;
        }
        leaf left {
            type string;
        }
        leaf leftid {
            type string;
        }
        leaf leftsubnet {
            type string;
        }
        leaf leftcert {
            type string;
        }
        leaf leftfirewall {
            type string;
        }
        leaf right {
            type string;
        }
        leaf rightid {
            type string;
        }
        leaf rightsubnet {
            type string;
        }
        leaf rightcert {
            type string;
        }
        leaf rightfirewall {
            type string;
        }
        leaf auto {
            type string;
        }
    }

    grouping rule {
        uses src-netaddress;
        uses dst-netaddress;
        leaf action {
            type int32;
        }
        leaf connectionName {
            type string;
        }
    }

    rpc conn-add {
        input {
            uses connection;
        }
        output {
            leaf result {
                type string;
            }
        }
    }

    rpc conn-all {
        input {
        }
        output {
            leaf result {
                type string;
            }
        }
    }

    rpc conn-del {
        input {
            leaf name {
                type string;
            }
        }
        output {
            leaf result {
                type string;
            }
        }
    }

    rpc rule-add {
        input {
            uses rule;
            leaf pos {
                type int32;
            }
        }
        output {
            leaf result {
                type string;
            }
        }
    }

    rpc rule-all {
        input {
        }
        output {
            leaf result {
                type string;
            }
        }
    }

    rpc rule-del {
        input {
            leaf position {
                type int32;
            }
        }
        output {
            leaf result {
                type string;
            }
        }
    }

    rpc gateway-all {
        input {
        }
        output {
            leaf result {
                type string;
            }
        }
    }

}
